module affinity-topology-all { 
    namespace "urn:opendaylight:affinity";
    prefix affinity;

    import ietf-inet-types { prefix inet; }
    import ietf-yang-types { prefix yang; }
    import yang-ext { prefix ext; }
    import opendaylight-inventory {prefix inv;}

    revision "2013-09-25" {
        description "Initial revision of affinity model to be reviewed";
    }

    typedef affinity-group-ref {
        type instance-identifier;
    }
    
    typedef affinity-link-ref {
        type instance-identifier;
    }

    grouping affinity-group {
        leaf id {
            type string;
        }   
        list affinity-identifiers {
            key id;
            uses affinity-identifier;
        }
    }

    grouping affinity-link {
        leaf id {
            type string;
        }
        leaf from-affinity-group {
            type affinity-group-ref;
        }
        leaf to-affinity-group {
            type affinity-group-ref;
        }
        leaf attribute {
            type string;
        }
    }

    grouping affinity-identifier {
        leaf id {
            type string;
        }
        // Address is either an IP address, IP prefix, or MAC address.
        leaf address {
            description "Mac or Inet address";
            type union {
                type inet:ip-address;
                type inet:ip-prefix;
                type yang:mac-address;
            }
        }
    }

    // Various types of affinity topologies. Used in union 'affinity-attribute'. 

    // Isolate flows according to certain constraints. 
    grouping isolate-path {
        leaf max-flows-per-link {
            type uint16;
        }
    }

    // Route through shortest path per l2/l3 semantics. 
    grouping shortest-path {
        leaf max-flows-per-link {
            type uint16;
        }
    }
   
    // oversubscription path
    grouping oversubscription-path {
        leaf max-link-oversubscription-percent {
            type uint16;
        }
    }

    // Affinity attribute. 
    grouping affinity-attribute {
        leaf id {
            type string;
        }
        choice attribute-type {
            description "affinity attribute";
            case isolate-path {
                 container isolate-path {
                     uses isolate-path;
                 }
            }
            case shortest-path {
                    container shortest-path {
                        uses shortest-path;
                    }
            }
            case oversubscription-path {
                    container oversubscription-path {
                        uses oversubscription-path;
                    }
            }
        }
    }

    identity affinity-group-context {
        description "Identity used to mark affinity-group context";
    }
    identity affinity-link-context {
        description "Identity used to mark affinity-link context";
    }
    
    container affinity-topology {
        list affinity-group {
            key id;
            ext:context-instance "affinity-group-context";
            uses affinity-group;
        }
        list affinity-link {
            key id;
            ext:context-instance "affinity-link-context";
            uses affinity-link;
        }
    }

    rpc create-affinity-group {
        input {
            uses affinity-group;
        }
    }
    rpc add-affinity-element {
        input {
            container element {
                uses affinity-identifier;
            }
            leaf group {
                type affinity-group-ref;
            }
        }
    }

    rpc get-affinity-groups {
        output {
            list affinity-group {
            key id;
            uses affinity-group;
            }
        }
    }
    rpc get-affinity-links {
    
    }
    rpc get-affinity-group {
    
    }
    rpc get-affinity-link {
    
    }
}
