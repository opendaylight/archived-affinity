module affinity-topology { 
    namespace "urn:opendaylight:affinity";
    prefix affinity;

    import ietf-inet-types { prefix inet; }
    import ietf-yang-types { prefix yang; }
    import yang-ext { prefix ext; }

    revision "2013-09-16" {
        description "Initial revision of affinity model";
    }

    typedef affinity-group-ref {
        type instance-identifier;
    }
    
    typedef affinity-link-ref {
        type instance-identifier;
    }

    grouping affinity-group {
        leaf id {
            type string;
        }   
        list affinity-identifier {
            key id;
            leaf id {
            type string;
            }
            leaf address {
                description "Mac or Inet address";
                type union {
                    type inet:ip-address;
                    type yang:mac-address;
                }
            }
        }
    }

    grouping affinity-link {
        leaf id {
            type string;
        }
        leaf from-affinity-group {
            type affinity-group-ref;
        }
        leaf to-affinity-group {
            type affinity-group-ref;
        }
        leaf attribute {
            type string;
        }
    }

    identity affinity-group-context {
        description "Identity used to mark affinity-group context";
    }
    identity affinity-link-context {
        description "Identity used to mark affinity-link context";
    }

    container affinity-topology {
        list affinity-group {
            key id;
            ext:context-instance "affinity-group-context";
            uses affinity-group;
        }
        list affinity-link {
            key id;
            ext:context-instance "affinity-link-context";
            uses affinity-link;
        }
    }

    rpc get-affinity-groups {
        output {
            list affinity-group {
                key id;
                uses affinity-group;
            }
        }
    }
    rpc get-affinity-links {
    
    }
    rpc get-affinity-group {
    
    }
    rpc get-affinity-link {
    
    }
}
